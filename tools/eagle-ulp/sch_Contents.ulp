#usage "select sheet ; built contents sheet\n"

// Good to place into user menu with  MENU 'ru Cnt' ...;
// to have a replacement for the sheet select spin edit.

// On each sheet, a Frame is required the device name of which
// contains 'SheetFrame'.
// The value of the frame should be ON (changeable) and be visible
// through a text ">value" on it.
// Change the value to reflect the contents of the sheet.

// To build a contents sheet,
// - create a new sheet
// - place a SheetFrame on it
// - change the value to contain 'Contents'
//     -- no other SheetFrame value should contain 'Contents'
// - press the "Write Contents" button
// Result:
// - a Sheet:Value table is written,
// - all nets that cross sheet boarders are listed.

//- - - - - - - - - - - - - - - - - - - - - - - - - - - - - - - - - - - - - -
// user changeable values:

string Frame_device_name_Contains = "SheetFrame"; // case ignored
string ContentsFrame_value_Contains = "Contents"; // case ignored

int   cTextRatio  = 12;
int   cTextSize   = 70; // mil
int   cNameWidth  = ELEMENT_NAME_LENGTH;
int   cTableWidth = 32; // *cGridSize

int   cUseTmpFileForContents = 0; // 1=faster??

//############################################################################
//############################################################################
real  cGridSize   = 0.1;   // inch;

string         SheetValue[];
string         SheetArea[];
numeric string ListViewText[];
int            SheetCount;
int            FrameLeft[];
int            FrameTop[];
int            ContentsSheetNo;

//- - - - - - - - - - - - - - - - - - - - - - - - - - - - - - - - - - - - - -
numeric string NetNames[];
string         NetSheet[];   // gathered as '_**_*'  =^= sheet 1,2, 4,
                             // converted to __1__2_____4 for output
int            NetCount;
string         NetSheetInit;

int            X0, Y0;

//############################################################################
string RealStr( real aArg )
{
string iResult;
int    i;
  sprintf( iResult, "%f", aArg );
  for( i=strlen(iResult)-1 ; i>0 ; i-- ) {
    if( iResult[i]=='0' ) {iResult[i]=0;  continue; };
    if( iResult[i]=='.' )  iResult[i]=0;  break;
  };

  return iResult;
}

//---------------------------------------------------------------------------
string RealCoord( real aX, real aY )
{
  return "(" + RealStr(aX) + " " + RealStr(aY) + ")" ;
}

//---------------------------------------------------------------------------
string GridCoord( int aX, int aY )  // -> (aX*cGridSize aY*cGridSize)
{
  return RealCoord( aX*cGridSize, aY*cGridSize );
}

//############################################################################
void FindFrames(void)
{
int i;
string iFrameName = strlwr(Frame_device_name_Contains);
  schematic(SCH) SCH.sheets(SH) {
    int     iFound=0;
    string  iValue;
    int     iX1,iY1,iX2,iY2, iSwap;
    SH.parts(P) {
      if( strstr(strlwr(P.device.name), iFrameName) < 0 ) continue;
      iFound = 1;
      iValue = P.value;
      P.instances(I) {
        iX1 = I.x + I.gate.symbol.area.x1;  iY1 = I.y + I.gate.symbol.area.y1;
        iX2 = I.x + I.gate.symbol.area.x2;  iY2 = I.y + I.gate.symbol.area.y2;
      };
      break;
    };
    if(!iFound) {
      iValue="<No " + Frame_device_name_Contains + ">";
      iX1 = SH.area.x1;  iY1 = SH.area.y1;
      iX2 = SH.area.x2;  iY2 = SH.area.y2;
    };
    if( iX1 > iX2 ) { iSwap = iX1; iX1 = iX2; iX2 = iSwap; };
    if( iY1 > iY2 ) { iSwap = iY1; iY1 = iY2; iY2 = iSwap; };

    SheetValue[SheetCount] = iValue;
    FrameLeft[ SheetCount] = iX1;
    FrameTop[  SheetCount] = iY2;

    sprintf( SheetArea[SheetCount], "%s %s"
             , RealCoord( u2inch(iX1), u2inch(iY1)-0.02 )
             , RealCoord( u2inch(iX2), u2inch(iY2)+0.02 ) );
    SheetCount++;
  };

  // MakeListViewText
  for( i=0 ; i<SheetCount ; i++ ) {
    sprintf( ListViewText[i], "      %d\t%s", i+1, SheetValue[i] );
  };
}

//---------------------------------------------------------------------------
string EDIT_sheet( int aSheetNo )
{
string iVisibleLayers;
string iResult;

  schematic(SCH) SCH.layers(L) {
    string iBuf;
    if( ! L.visible ) continue;

    if( L.number == 94 ) sprintf(iBuf, " 94 -95 -96"   );
    else                 sprintf(iBuf, " %d", L.number );

    iVisibleLayers += iBuf;
  };

  sprintf( iResult, "grid inch;\n"
                    "dis  none;\n"
                    "edit .s%d;\n"
                    "win  %s;\n"
                    "dis  %s;\n"
                   , aSheetNo
                   , SheetArea[aSheetNo-1]
                   , iVisibleLayers );
                   
  return iResult;
}

//############################################################################
void EnterNet( string aName, int aSheetNo )
{
int iNet, i;
string iSheet;

  if( aSheetNo==ContentsSheetNo )  return;

  for(iNet=0; iNet<NetCount; iNet++ ) {
    if(NetNames[iNet]==aName) break;
  };

  if(iNet>=NetCount) {
    NetCount++;
    NetNames[iNet] = aName;
    NetSheet[iNet] = NetSheetInit;
  };

  iSheet=NetSheet[iNet];
  iSheet[aSheetNo]='*';
  NetSheet[iNet]=iSheet;
}

//---------------------------------------------------------------------------
void RemoveSingleSheetNets(void)
{
int i, j, s, iFirst,iLast;
string iSheet;

  j=0;
  for(i=0;i<NetCount;i++) {
    iSheet = NetSheet[i];
    iFirst = 12345678;

    for(s=0;iSheet[s];s++) if(iSheet[s]=='*') {
      if(iFirst==12345678) iFirst=s;
                           iLast =s;
    };

    if(iFirst!=12345678) if(iFirst!=iLast) {
      NetNames[j] = NetNames[i];
      NetSheet[j] = NetSheet[i];
      j++;
    }
  }

  NetCount=j;
}

//---------------------------------------------------------------------------
void SortNetNames(void)
{
int    i;
int    iIndex[];
string iTmp[];

  //-- Sort NetNames[]:NetSheet[] after Netnames

  sort( NetCount, iIndex, NetNames, NetSheet );

  for(i=0;i<NetCount;i++) iTmp[i] = NetNames[iIndex[i]];
  for(i=0;i<NetCount;i++) NetNames[i] = iTmp[i];

  for(i=0;i<NetCount;i++) iTmp[i] = NetSheet[iIndex[i]];
  for(i=0;i<NetCount;i++) NetSheet[i] = iTmp[i];
}

//---------------------------------------------------------------------------
void ConvertNetSheet(void)
{
int    iNet, i;
string iSheet, iBuf, iSheetOut;
string iValidSheet = NetSheetInit;

  // Find ValidSheet
  for( iNet=0 ; iNet<NetCount ; iNet++ ) {
    iSheet = NetSheet[iNet];
    for( i=0 ; ; i++ ) {
      char iCh = iSheet[i];  if(!iCh) break;
      if( iCh=='*' ) iValidSheet[i]='*';
    };
  };

  // turn NetSheet "_*_*_"  into "__2___4_"
  for( iNet=0 ; iNet<NetCount ; iNet++ ) {
    iSheetOut = "";
    iSheet    = NetSheet[iNet];

    for( i=0 ; iSheet[i] ; i++ ) {
      if( iValidSheet[i]!='*') continue;
      if( iSheet[i]=='*' ) {
        if( i<10 ) sprintf( iBuf, "__%d", i );        
        else       sprintf( iBuf,  "_%d", i );
        iSheetOut += iBuf;
      }else{
        iSheetOut += "___";
      };
    };

    NetSheet[iNet] = iSheetOut;
  };
}

//###########################################################################
/*
string NewString[];
int    NewX[], NewY[], NewLayer[];
int    nNew;
*/
void NewString_Enter( string aString, int aX, int aY, int aLayer )
{
/*
  NewString[nNew] = aString;
  NewX     [nNew] = aX;
  NewX     [nNew] = aY;
  NewLayer [nNew] = aLayer;
  nNew++;
*/
}

//---------------------------------------------------------------------------
string PrintSheetNets( int aX, int aY, int aNetNo )
{
string iResult;

  NewString_Enter( " " + NetNames[aNetNo], aX           , aY, 91 );
  NewString_Enter(       NetSheet[aNetNo], aX+cNameWidth, aY, 91 );

  //sprintf( iResult, "Text ' %-*s' %s; Text '%s' %s;\n"
  //                , ELEMENT_NAME_LENGTH+1
  sprintf( iResult, "Text ' %s' %s; Text '%s' %s;\n"
                  , NetNames[ aNetNo]
                  , GridCoord( aX, aY )
                  , NetSheet[aNetNo]
                  , GridCoord( aX+cNameWidth, aY ) );
  return iResult;
}

//---------------------------------------------------------------------------
string PrintNets(void)
{
string iResult="";
string iBuf;
int    x, y, i;
string iSheet;

  if(!NetCount) return iResult;

  NewString_Enter( " Global Nets", X0, Y0-1, 91 );

  iResult = "change layer 91;\nText ' Global Nets' " + GridCoord(X0,Y0-1) + ";\n"
          + "dis none;\n"
          + "change font prop;\n" + iResult + "\n" ;

  x = X0-cTableWidth;
  y = -999;

  for(i=0;i<NetCount;i++) {
    if( y<2 ) {
      y = Y0;
      x = x + cTableWidth;
      --y;
    };

    --y;

    iResult += PrintSheetNets( x, y, i );
  };

  return iResult + "\n";
}

//---------------------------------------------------------------------------
int GetTextInt( int aDefault, string aText, string aTag )
{
int iPos;
int iFirstDigit = -1;
int i;
string iBuf="";
  iPos = strstr(aText,aTag);  if( iPos < 0 ) return aDefault;

  for( i=iPos+strlen(aTag) ; aText[i] ; i++ ) {
    if( ('0' <= aText[i]) && (aText[i] <= '9') ) {
      iFirstDigit = i;
      break;
    };
  };
  if( iFirstDigit < 0 ) return aDefault;

  for( i=iFirstDigit ; aText[i] ; i++ ) {
    if( ('0' <= aText[i]) && (aText[i] <= '9') ) {
      iBuf += aText[i];
    }else{
      break;
    };
  };

  i = strtol( iBuf);
  if( iFirstDigit>0 ) if( aText[iFirstDigit-1]=='-' ) i = -1;
  return i;
}

//###########################################################################
/*
string OldString[];
int    OldX[], OldY[], OldLayer[];
int    nOld;
*/
void OldString_Enter( string aString, int aX, int aY, int aLayer, int aSize, int aRatio )
{
/*
  OldString[nOld] = aString;
  OldX     [nOld] = aX;
  OldX     [nOld] = aY;
  OldLayer [nOld] = aLayer;
  nOld++;
*/
}

//---------------------------------------------------------------------------
void WriteContents_Begin(void)
{
string iContents = strlwr(ContentsFrame_value_Contains);

  //- - - - - - - - - - - - - - - - - - - - - - - - - - - - - - - - - - - -
  // Find contents sheet

  for( ContentsSheetNo=1 ; ContentsSheetNo<=SheetCount ; ContentsSheetNo++ ) {
    if( strstr(strlwr(SheetValue[ContentsSheetNo-1]),iContents) >= 0 ) break;
  };
  if( ContentsSheetNo>SheetCount ) {
    return;
  };

  //- - - - - - - - - - - - - - - - - - - - - - - - - - - - - - - - - - - -
  // Get old cTextRatio / cTextSize / cTableWidth

  schematic(SCH) SCH.sheets(SH) {
    if( SH.number != ContentsSheetNo ) continue;
    {
      int iFirstNameX;
      int iFirstName = 1;
      int iFirstNet  = 1;
      int iDone;
      iDone = 0;
      
      SH.texts(T) OldString_Enter( T.value,T.x,T.y,T.layer,T.size,T.ratio );

      SH.texts(T) {
        if(!iDone)
        if( T.layer==94 ) {
          cTextRatio = T.ratio;
          cTextSize  = round( T.size * u2mil(1) );
          iDone      = 1;
        };
      };
      iDone = 0;
      SH.texts(T) {
        if(!iDone)
        if( T.layer==91 ) {
          string iBuf = T.value;
          if( iBuf[0]==' ' ) {  // name
            if( iFirstName==1 ) {
              iFirstName  = 0 ;
              iFirstNameX = T.x;
            }else
            if( T.x != iFirstNameX ) {
              cTableWidth = round( u2inch(T.x-iFirstNameX) / cGridSize );
              if(cTableWidth<0) cTableWidth=-cTableWidth;
              iDone  = 1;
            };
          };
          if( iBuf[0]=='_' ) {  // net
            if( iFirstNet==1 ) {
              iFirstNet  = 0 ;
              cNameWidth = round( u2inch(T.x-iFirstNameX) / cGridSize );
              if(cNameWidth<0) cNameWidth=-cNameWidth;
            };
          };
        };
      };
    };
  };
};

//---------------------------------------------------------------------------
void WriteContents_End(void)
{
string iContentTextDel;
string iNewContents = "";
string iContents = strlwr(ContentsFrame_value_Contains);
string iCmd;
string iBuf;
int    i;
real   iTextSize = cTextSize;
       iTextSize = iTextSize / 1000;

  //- - - - - - - - - - - - - - - - - - - - - - - - - - - - - - - - - - - -
  // Find contents sheet

  for( ContentsSheetNo=1 ; ContentsSheetNo<=SheetCount ; ContentsSheetNo++ ) {
    if( strstr(strlwr(SheetValue[ContentsSheetNo-1]),iContents) >= 0 ) break;
  };
  if( ContentsSheetNo>SheetCount ) {
    dlgMessageBox( "No SheetFrame value contains '"
                   + ContentsFrame_value_Contains + "'" );
    return;
  };

  //- - - - - - - - - - - - - - - - - - - - - - - - - - - - - - - - - - - -
  // Delete old contents

  schematic(SCH) SCH.sheets(SH) {
    int iLayer;
    int cLayers[] = {91,94};
    int cNLayers  = 2;
    if( SH.number != ContentsSheetNo ) continue;
    for( iLayer=0 ; iLayer<cNLayers ; iLayer++ ) {
      string iBuf = "";
      SH.texts(T) {
        if( T.layer==cLayers[iLayer] ) {
          iBuf += " " + RealCoord( u2inch(T.x), u2inch(T.y) ) + "\n";
        };
      };
      if( iBuf != "" ) {
        sprintf( iBuf, "Dis none %d;\nDel %s;\n", cLayers[iLayer], iBuf );
        iContentTextDel += iBuf;
      };
    };
  };

  //- - - - - - - - - - - - - - - - - - - - - - - - - - - - - - - - - - - -
  // Print Sheet Values

  X0 = round(  u2inch(FrameLeft[ContentsSheetNo-1])                / cGridSize +0.5);
  Y0 = round( (u2inch(FrameTop [ContentsSheetNo-1])-iTextSize*1.1) / cGridSize -0.5);

  NewString_Enter( " Sheet Value", X0, Y0, 94 );
  sprintf( iBuf, "text ' Sheet Value' %s;\n", GridCoord(X0,Y0) );
  iNewContents += iBuf;

  for( i=0 ; i<SheetCount ; i++ ) {
    Y0--;
    
    sprintf(iBuf, "'  %2d   %s'", i+1, SheetValue[i] );
    NewString_Enter( iBuf, X0, Y0, 94 );
    iNewContents += "text " + iBuf + " " + GridCoord( X0, Y0 ) + ";\n";
  };

  sprintf( iCmd, "%s\n"
                 "change layer 94;\n"
                 "change size %s;\n"
                 "change ratio %d;\n"
                 "%s"
                 "%s\n"
               , EDIT_sheet( ContentsSheetNo )
               , RealStr(iTextSize)
               , cTextRatio
               , iContentTextDel
               , "dis none;\n" + iNewContents
         );

  //- - - - - - - - - - - - - - - - - - - - - - - - - - - - - - - - - - - -
  // Print Global Nets

  // Gather Nets
  for( i=0 ; i<=SheetCount ; i++ ) NetSheetInit += "_";

  schematic(SCH) {
    SCH.sheets(SH) SH.nets(N)   EnterNet(N.name,SH.number);
  };
  RemoveSingleSheetNets();
  SortNetNames();
  ConvertNetSheet();

  // Print Nets
  Y0--;
  iCmd += PrintNets();

  //- - - - - - - - - - - - - - - - - - - - - - - - - - - - - - - - - - - -
  // exit(iCmd)

  iCmd = iCmd + "dis none 91 92 94 95 96;\n";
  if(cUseTmpFileForContents) {
    string iFileName;
    schematic(S) iFileName = filedir(S.name) + "tmp$cnt.scr";
    output(iFileName) printf("%s",iCmd);  exit("scr " + iFileName);
  }else{
    exit(iCmd);
  };
}

//###########################################################################
void HelpDialog(void)
{
string iText;
  fileread(iText, argv[0]);

  dlgDialog("Cnt.ulp Help") {
    dlgGridLayout {
      dlgCell(0, 0, 100, 100) {
        dlgVBoxLayout {
          dlgLabel("&Help text");
          dlgTextView(iText);
        };
      };
    };
  };
}

//---------------------------------------------------------------------------
void RunContentsDialog(void)
{
int iSelected = 0;

  WriteContents_Begin();

  dlgDialog("Cnt.ulp") {
    dlgHBoxLayout {
      dlgLabel("Text &Ratio:   ");         
      dlgIntEdit(cTextRatio , 1,  100);
    };
    dlgHBoxLayout {
      dlgLabel("Text Si&ze:     ");
      dlgIntEdit(cTextSize  , 1, 1000);
    };
    dlgHBoxLayout {
      dlgLabel("&Name Width:");
      dlgIntEdit(cNameWidth, 0, 1000);
    };
    dlgHBoxLayout {
      dlgLabel("Table &Width:");
      dlgIntEdit(cTableWidth, 0, 1000);
    };

    dlgHBoxLayout {
      dlgPushButton("+OK")    {
        WriteContents_End();
      };
      dlgPushButton("Cancel") { dlgReject(); };
    };
  };
}

//---------------------------------------------------------------------------
void RunDialog(void)
{
int iSelected = 0;
  sheet(SH) iSelected = SH.number-1;

  dlgDialog("Cnt.ulp") {
    dlgHBoxLayout {
      dlgPushButton("Write Contents...") { RunContentsDialog();}; 
      //dlgPushButton("Write Contents") { WriteContents(); };

      dlgPushButton("Help") { HelpDialog(); };
    };

    dlgLabel("&Sheet");
    dlgListView("Number\tValue", ListViewText, iSelected) {
      exit( EDIT_sheet(iSelected+1) );
    };

    dlgHBoxLayout {
      dlgPushButton("+OK")    {
        exit( EDIT_sheet(iSelected+1) );
      };
      dlgPushButton("Cancel") { dlgReject(); };
    };
  };
}

//############################################################################
// main()
{
  FindFrames();

  RunDialog();
}
