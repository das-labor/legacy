// brd_DisplaySets -- EAGLE 4.09 user language program          RS 20 Apr 2008
// Show a dialog to select a DISPLAY setting from stored ones

#include "IniFile.ulp"

string SetNames[];   // Names of the Sets
string SetLayers[];  // "1 2 4 33 ..."
int    SetCount;     // number of sets
int    Changed;      // if 1 : Store changes on exit

//###########################################################################
/*
string Board_GetLayers(UL_BOARD B)
{
string result; int i;
  B.layers(L) if(i<L.number) i=L.number;
  for(;i>=0;i--) result[i]='.';  // nonzero = mark that string not ending here
  B.layers(L) if(L.used) result[L.number]='0'+L.visible;
  return result;
}

//---------------------------------------------------------------------------
string Layers_Display(string Layers)
{
string result; int i;
  while(Layers[++i]) if(Layers[i]>='0') {
    if( Layers[i]<'1' ) result +='-';
    sprintf(result,"%s%d ",result,i);
  };
  return "DISPLAY " + result + ";\n";
}
*/

//###########################################################################
string GetCurrentVisibleLayers(void)
{
int    iLayers[];
int    iLayerCount=0;
string iResult;
int    i;
  board(B) B.layers(L) {
    if( L.visible ) {
      iLayers[iLayerCount] = L.number;
      ++iLayerCount;
    };
  };

  sort( iLayerCount, iLayers );

  iResult = "";
  for( i=0 ; i<iLayerCount ; i++ ) {
    sprintf( iResult, "%s %d", iResult, iLayers[i] );
  };

  return iResult;
}

//===========================================================================
void ReadSets(void)
{
string cLast = "<Last>";
string iLines[];
int    iCount, i, j, iDest;
string iCurrentCommand = GetCurrentVisibleLayers();

  iCount = Settings_GetInteger("SetCount", 0);

  // get names and layers
  for( i=0 ; i<iCount ; i++ ) {
    string iLineBuf, iNameBuf, iLayerBuf;
    
    sprintf( iLineBuf, "Set%d", i+1 );
    iLineBuf = Settings_GetString(iLineBuf, "");

    if( iLineBuf[0] != '\t' ) continue;

    iNameBuf  = "";
    iLayerBuf = "";
    iDest       = 0 ;
    for( j=0 ; iLineBuf[j] ; j++ ) {
      if(j==0) continue;
      if( iLineBuf[j]=='\t' ) { iDest=1; continue; };
      if(!iDest) iNameBuf  += iLineBuf[j];
      else       iLayerBuf += iLineBuf[j];
    };
    SetNames [SetCount] = iNameBuf ;
    SetLayers[SetCount] = iLayerBuf;
    ++SetCount;
  };

  // find current
  for( i=0 ; i<SetCount ; i++ ) {
    if(SetLayers[i]==iCurrentCommand ) break;
  };
  // add if not found
  if( i==SetCount ) {
    if( SetCount && (SetNames[SetCount-1]==cLast) ) --SetCount;
    Changed=1;
    SetNames [SetCount] = cLast;
    SetLayers[SetCount] = iCurrentCommand;
    ++SetCount;
  };
}

//===========================================================================
int ChangeLayerSet(int aSelected)
{
string iName = SetNames[aSelected];
string iBuf;
int    iDlgResult;

  if(!SetCount) return 0;

  dlgDialog("Change Layer Set") {
    dlgHBoxLayout { dlgLabel("&Name:");  dlgStringEdit(iName);  };
    dlgHBoxLayout {
      dlgPushButton("+Rename" ) {  dlgAccept();  iDlgResult= 1; };
      dlgPushButton("Delete"  ) {  dlgAccept();  iDlgResult=-1; };
      dlgPushButton("-Cancel" ) {  dlgReject();  iDlgResult= 0; };
    };
  };

  switch(iDlgResult) {
    case  1: Changed = 1;
             SetNames[aSelected] = iName;
             return aSelected;

    case -1: Changed = 1;
             for( int i=aSelected+1 ; i<SetCount ; i++ ) {
               SetNames [i-1] = SetNames [i];
               SetLayers[i-1] = SetLayers[i];
             };
             --SetCount;
             SetNames[SetCount] = "";
             if( aSelected ) return aSelected-1;
             return aSelected;

    default: return aSelected;
  };
}

//===========================================================================
int MoveEntry(int aSelected, int aUp)
{
string iSwap;  int iNewSel;

  if(aUp<0) {
    if(aSelected<=0)          return aSelected;
    iNewSel = aSelected-1;
  }else{
    if(aSelected>=SetCount-1) return aSelected;
    iNewSel = aSelected+1;
  };

  Changed = 1;

  iSwap                  = SetNames [aSelected];
  SetNames [aSelected]   = SetNames [iNewSel  ];
  SetNames [iNewSel  ]   = iSwap               ;

  iSwap                  = SetLayers[aSelected];
  SetLayers[aSelected]   = SetLayers[iNewSel  ];
  SetLayers[iNewSel  ]   = iSwap               ;

  return iNewSel;
}

//===========================================================================
void WriteSets(void)
{
int i;
string iNameBuf, iBuf;

  if(!Changed) return;
 
  Settings_PutInteger("SetCount", SetCount );

  for( i=0 ; i<SetCount ; i++ ) {
     sprintf( iNameBuf, "Set%d", i+1 );
     sprintf( iBuf, "\t%s\t%s\n", SetNames[i], SetLayers[i] );
     Settings_PutString(iNameBuf, iBuf);
  };
}

//===========================================================================
void Exit_Selected(int aSelected)
{
int i;
string iLayers;
string iCommand = "DIS none ";

  WriteSets();

  iLayers = SetLayers[aSelected];

  for( ; iLayers!="" ; ) {
    string iBuf  = "";
    string iRest = "";
    int iSel=0;
    for( i=0 ; iLayers[i] ; i++ ) {
      if(!iSel) iBuf  += iLayers[i];
      else      iRest += iLayers[i];
      if( iLayers[i]==' ' ) iSel=1;
    };
    iLayers = iRest;
    iCommand += iBuf;
    if( (iBuf=="21") || (iBuf==" 21") || (iBuf=="21 ") ) { // tPlace
      iCommand += " -tOrigins -tDocu -tNames -tValues ";
    };
    if( (iBuf=="22") || (iBuf==" 22") || (iBuf=="22 ") ) { // bPlace
      iCommand += " -bOrigins -bDocu -bNames -bValues ";
    };
  };

  exit( iCommand+';' );
}

//===========================================================================
void RunDialog(void)
{
int iSelected = 0;
  {
    int   i;
    string iCurrentCommand = GetCurrentVisibleLayers();
    for( i=0 ; i<SetCount ; i++ ) {
      if(SetLayers[i]!=iCurrentCommand ) continue;
      iSelected = i;
      break;
    };
  };

  dlgDialog("  brd_DisplaySets.ulp") {
    dlgHBoxLayout{
      dlgListBox( SetNames, iSelected) {
        Exit_Selected(iSelected);
      };

      dlgVBoxLayout{
        dlgPushButton( "&Change.." ) {
          iSelected = ChangeLayerSet(iSelected);
          dlgRedisplay();
        };

        dlgPushButton( "&Up"   ) { iSelected = MoveEntry(iSelected, -1); };
        dlgPushButton( "Dow&n" ) { iSelected = MoveEntry(iSelected,  1); };

        dlgPushButton("Set Used Layers.." ) {
          WriteSets();
          dlgReject();
          exit("run brd_UseLayers;");
        };
        dlgPushButton("Save/Select Color Set") {
          WriteSets();
          dlgReject();
          exit("run brd_LayerColors;");
        };
        dlgPushButton("-Cancel" ) { dlgReject(); };
        dlgPushButton("+&OK"   ) { Exit_Selected(iSelected); };
      };
    };
  };
}


//###########################################################################
// main()
{
  ReadSets();
  RunDialog();
}
