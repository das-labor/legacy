// brd_LayerColors.ulp -- EAGLE 4.09 user language program      RS 10 Mar 2003
// Show a dialog to select a DISPLAY setting from stored ones

#include "IniFile.ulp"

/*
Layer color	         SET COLOR_LAYER layer color;
Fill pattern for layer	 SET FILL_LAYER layer fill;
*/

string SetNames[];   // Names of the Sets
string SetLayers[];  // "1 2 4 33 ..."
int    SetCount;     // number of sets
int    Changed;      // if 1 : dialog("Store changes") on exit

int LayerNumbers[];
int LayerColors[];
int LayerFills[];
int LayerCount;

//###########################################################################
void GetLayers(void)
{
  board(B) B.layers(L) {
    LayerNumbers[LayerCount] = L.number;
    LayerColors [LayerCount] = L.color;
    LayerFills  [LayerCount] = L.fill;
    ++LayerCount;
  };
}

//###########################################################################
string GetCurrentLayers(void)
{
numeric string iLayers[];
int    iLayerCount=0;
string iResult;
int    i;
  board(B) B.layers(L) {
    sprintf( iLayers[iLayerCount], "%d %d %d", L.number, L.color, L.fill );
    ++iLayerCount;
  };

  sort( iLayerCount, iLayers );

  iResult = "";
  for( i=0 ; i<iLayerCount ; i++ ) {
    if(iResult=="") iResult = iLayers[i];
    else            sprintf( iResult, "%s\t%s", iResult, iLayers[i] );
  };

  return iResult;
}

//===========================================================================
void ReadSets(void)
{
string cLast = "<Last>";
string iLines[];
int    iCount, i, j, iDest;
string iCurrentLayers = GetCurrentLayers();

  iCount = Settings_GetInteger("SetCount", 0);

  // get names and layers
  for( i=0 ; i<iCount ; i++ ) {
    string iLineBuf, iNameBuf, iLayerBuf;

    sprintf( iLineBuf, "Set%d", i+1 );
    iLineBuf = Settings_GetString(iLineBuf, "");

    if( iLineBuf[0] != '\t' ) continue;

    iNameBuf    = "";
    iLayerBuf = "";
    iDest       = 0 ;
    for( j=0 ; iLineBuf[j] ; j++ ) {
      if(j==0) continue;
      if(iDest) iLayerBuf += iLineBuf[j];
      else
      if( iLineBuf[j]=='\t' ) iDest=1;
      else iNameBuf += iLineBuf[j];
    };
    SetNames [SetCount] = iNameBuf ;
    SetLayers[SetCount] = iLayerBuf;
    ++SetCount;
  };

  // find current
  for( i=0 ; i<SetCount ; i++ ) {
    if(SetLayers[i]==iCurrentLayers ) break;
  };
  // add if not found
  if( i==SetCount ) {
    if( SetCount && (SetNames[SetCount-1]==cLast) ) --SetCount;
    Changed=1;
    SetNames [SetCount] = cLast;
    SetLayers[SetCount] = iCurrentLayers;
    ++SetCount;
  };
}

//===========================================================================
int ChangeLayerSet(int aSelected)
{
string iName = SetNames[aSelected];
string iBuf;
int    iDlgResult;
int    i;

  if(!SetCount) return 0;

  dlgDialog("Change Layer Set") {
    dlgHBoxLayout {
      dlgLabel("&Name:");
      dlgStringEdit(iName);
    };
    dlgHBoxLayout {
      dlgPushButton("Rename"  ) { iDlgResult= 1; dlgAccept(); };
      dlgPushButton("Delete"  ) { iDlgResult=-1; dlgAccept(); };
      dlgPushButton("+Cancel" ) { iDlgResult= 0; dlgReject(); };
    };
  };

  switch(iDlgResult) {
    case  1: Changed = 1;
             SetNames[aSelected] = iName;
             return aSelected;

    case -1: Changed = 1;
             for( i=aSelected+1 ; i<SetCount ; i++ ) {
               SetNames   [i-1] = SetNames   [i];
               SetLayers[i-1] = SetLayers[i];
             };
             --SetCount;
             SetNames[SetCount] = "";
             if( aSelected ) return aSelected-1;
             return aSelected;

    default: return aSelected;
  };
}

//===========================================================================
int MoveEntryUp(int aSelected)
{
string iSwap;
  if(aSelected<=0) return aSelected;

  Changed = 1;

  iSwap                    = SetNames   [aSelected  ];
  SetNames   [aSelected  ] = SetNames   [aSelected-1];
  SetNames   [aSelected-1] = iSwap                   ;

  iSwap                    = SetLayers[aSelected  ];
  SetLayers[aSelected  ] = SetLayers[aSelected-1];
  SetLayers[aSelected-1] = iSwap                   ;

  return aSelected-1;
}

//- - - - - - - - - - - - - - - - - - - - - - - - - - - - - - - - - - - - - -
int MoveEntryDown(int aSelected)
{
string iSwap;
  if(aSelected>=SetCount-1) return aSelected;

  Changed = 1;

  iSwap                    = SetNames   [aSelected  ];
  SetNames   [aSelected  ] = SetNames   [aSelected+1];
  SetNames   [aSelected+1] = iSwap                   ;

  iSwap                    = SetLayers[aSelected  ];
  SetLayers[aSelected  ] = SetLayers[aSelected+1];
  SetLayers[aSelected+1] = iSwap                   ;

  return aSelected+1;
}

//===========================================================================
void WriteSets()
{
int i;
string iNameBuf, iBuf;

  if(!Changed) return;

  Settings_PutInteger("SetCount", SetCount );

  for( i=0 ; i<SetCount ; i++ ) {
     sprintf( iNameBuf, "Set%d", i+1 );
     sprintf( iBuf, "\t%s\t%s\n", SetNames[i], SetLayers[i] );
     Settings_PutString(iNameBuf, iBuf);
  };
}

//===========================================================================
string ChangeLayer( string aCtrl )
{
int    iNumber, iColor, iFill;
string iNumberBuf="", iColorBuf="", iFillBuf="";
int    i, j;
string iResult = "";

  //scan control string;
  j=0;
  for( i=0 ; aCtrl[i] ; i++ ) {
    if( aCtrl[i]==' ' ) j++;
    else
    switch(j) {
      case 0: iNumberBuf += aCtrl[i]; break;
      case 1: iColorBuf  += aCtrl[i]; break;
      case 2: iFillBuf   += aCtrl[i]; break;
    };
  };
  iNumber = strtol(iNumberBuf);
  iColor  = strtol(iColorBuf );
  iFill   = strtol(iFillBuf  );

  //find iNumber
  for( i=0 ; i<LayerCount ; i++ ) {
     if( LayerNumbers[i]==iNumber ) break;
  };
  if( i==LayerCount ) return iResult;

  // build SET.. commands
  if( iColor != LayerColors[i] ) {
    sprintf( iResult, "%s SET COLOR_LAYER %d %d;", iResult, iNumber, iColor );
  };

  if( iFill != LayerFills[i] ) {
    sprintf( iResult, "%s SET FILL_LAYER %d %d;", iResult, iNumber, iFill );
  };

  if( iResult!="" ) iResult += "\n";

  return iResult;
}

//===========================================================================
void Exit_Selected(int aSelected)
{
int i;
string iLayers;
string iCommand;

  WriteSets();

  iLayers = SetLayers[aSelected];

  for( ; iLayers!="" ; ) {
    string iBuf  = "";
    string iRest = "";
    int iSel=0;
    for( i=0 ; iLayers[i] ; i++ ) {
      if( (!iSel) && (iLayers[i]=='\t') ) iSel=1;
      else
      if(!iSel) iBuf  += iLayers[i];
      else      iRest += iLayers[i];
    };
    iLayers = iRest;

    iCommand += ChangeLayer(iBuf);
  };
  if( iCommand != "" ) iCommand += "win;" ;

  // output("tmp$.txt") printf("%s", iCommand); exit(0);
  exit(iCommand);
}

//===========================================================================
void RunDialog(void)
{
int iSelected = 0;
  {
    int   i;
    string iCurrentLayers = GetCurrentLayers();
    for( i=0 ; i<SetCount ; i++ ) {
      if(SetLayers[i]!=iCurrentLayers ) continue;
      iSelected = i;
      break;
    };
  };

  dlgDialog("Color Sets") {
    dlgHBoxLayout{
      dlgListBox( SetNames, iSelected) {
        Exit_Selected(iSelected);
      };

      dlgVBoxLayout{
        dlgPushButton( "&Up"   ) { iSelected = MoveEntryUp(iSelected);   };
        dlgPushButton( "Dow&n" ) { iSelected = MoveEntryDown(iSelected); };

        dlgPushButton( "&Change.." ) {
          iSelected = ChangeLayerSet(iSelected);
          dlgRedisplay();
        };

        dlgPushButton("-Cancel") { WriteSets(); dlgReject(); };
        dlgPushButton("+&OK"   ) { Exit_Selected(iSelected); };
      };
    };
  };
}


//###########################################################################
// main()
{
  GetLayers();
  ReadSets();
  RunDialog();
}
